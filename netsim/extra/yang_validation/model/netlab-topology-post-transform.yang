module netlab-topology-post-transform {
  yang-version 1.1;
  namespace "urn:netlab:topology:post-transform";
  prefix "netlab-post";

  import netlab-topology-init {
    prefix netlab-init;
    revision-date 2025-12-12;
  }
  import netlab-topology-setup {
    prefix setup;
    revision-date 2025-12-12;
  }

  description
    "YANG model for netlab lab topology validation at Post-transform phase.
     This model validates the topology after all transformations are complete, when:
     - All node and link transformations are done
     - Interfaces have been created on nodes and links
     - All internal attributes have been added (sources, pools, Plugin, Provider, input)
     - Topology is in its final state ready for deployment
     
     At this phase:
     - Nodes are lists with IDs, management IPs, loopback addresses, and interfaces
     - Links are lists with linkindex, interfaces, and node_count
     - Interfaces have ifindex, ifname, ipv4, ipv6, linkindex, type attributes
     - defaults.sources is present
     - Internal structures (pools, Plugin, Provider, input) are present";

  revision 2025-12-12 {
    description "Initial version for post-transform phase validation";
  }

  container topology {
    description
      "Network lab topology structure at post-transform phase (final transformed state).";
    
    // Use defaults grouping (unchanged)
    container defaults {
      uses netlab-init:defaults-grouping;
    }

    // Redefine nodes as dictionary (container) with post-transform structure
    container nodes {
      description
        "Lab devices (nodes) at post-transform phase. Nodes are stored as
         a dictionary keyed by node name. Nodes have IDs, interfaces with
         addressing, and other transformed attributes.";
      anydata node_dict {
        description
          "Dictionary of nodes keyed by node name. Each node has attributes
           like id (mandatory), device, interfaces (with ipv4, ipv6, ifname,
           linkindex, type, mtu, ospf container), module, af, and module-specific attributes.";
      }
    }

    // Redefine links list with post-transform structure
    list links {
      key "linkindex";
      description
        "Links between lab devices at post-transform phase. Links have
         interfaces with addressing and other transformed attributes.";
      
      leaf linkindex {
        type uint32 {
          range "1..max";
        }
        description
          "Link sequence number (starting with one), used to generate default
           bridge names in libvirt. This is a read-only attribute set during
           topology transformation.";
      }
      
      // Redefine interfaces list with post-transform fields
      list interfaces {
        key "node";
        description
          "Interfaces connected by this link at post-transform phase.
           Interfaces have been created with addressing and other attributes.";
        min-elements 1;
        
        leaf node {
          type string;
          mandatory true;
          description
            "Node name. Note: Cannot use leafref to validate node existence since
             nodes are stored as a dictionary (anydata).";
        }
        
        leaf ipv4 {
          type union {
            type boolean;
            type string;
          }
          description "IPv4 address";
        }
        
        leaf ipv6 {
          type union {
            type boolean;
            type string;
          }
          description "IPv6 address";
        }
        
        leaf ifindex {
          type uint32 {
            range "0..max";
          }
          description "Interface index";
        }
        
        leaf ifname {
          type string;
          description "Interface name";
        }
        
        anydata interface_attrs {
          description "Other interface attributes (flexible structure for user-defined attributes)";
        }
      }
      
      // Link attributes
      leaf name {
        type string;
        description "Link name. Used for identification and in some provider configurations.";
      }
      
      leaf type {
        type enumeration {
          enum p2p;
          enum lan;
          enum stub;
          enum loopback;
          enum tunnel;
          enum vlan_member;
          enum lag;
        }
        description
          "Link type. When missing, link type is selected based on the number of devices
           connected to the link.";
      }
      
      leaf role {
        type enumeration {
          enum stub;
          enum passive;
          enum external;
        }
        description
          "Link role. Can be set to 'stub' for stub links, 'passive' for passive
           links in routing modules, or 'external' for external links (e.g., EBGP).";
      }
      
      leaf pool {
        type string;
        description
          "Address pool name to use for this link. References a pool defined
           in the addressing element.";
      }
      
      anydata prefix {
        description
          "Prefix for this link. Can be a string (IPv4 CIDR or prefix name), 
           a dictionary with ipv4/ipv6/allocation keys, or false (for layer-2-only links).";
      }
      
      leaf bandwidth {
        type uint32 {
          range "1..max";
        }
        description
          "Link bandwidth in Mbps. Used to configure interface bandwidth
           when supported by the connected device(s).";
      }
      
      leaf mtu {
        type uint32 {
          range "64..9216";
        }
        description "Link MTU. Valid range: 64-9216 bytes.";
      }
      
      leaf node_count {
        type uint32 {
          range "1..max";
        }
        description "Number of nodes connected to this link";
      }
      
      leaf bridge {
        type string;
        description
          "Bridge name for this link. Used in libvirt provider to specify
           the Linux bridge name for the link.";
      }
      
      container ra {
        description
          "IPv6 Router Advertisement (RA) configuration for this link.";
        leaf disable {
          type boolean;
          description
            "Disable Router Advertisements on this link.";
        }
        leaf slaac {
          type boolean;
          description
            "Enable Stateless Address Autoconfiguration (SLAAC).";
        }
        leaf dhcp {
          type string;
          description
            "DHCP configuration: 'all' or 'other'.";
        }
        leaf onlink {
          type boolean;
          description
            "Advertise on-link prefix.";
        }
        anydata ra_config {
          description
            "Additional RA configuration attributes (flexible structure)";
        }
      }
      
      anydata link_attrs {
        description
          "Additional link attributes (flexible structure)";
      }
      
      must "count(interfaces/node) >= 2 or type = 'stub' or type = 'loopback' or not(type)" {
        error-message "Link must connect at least two nodes (unless it's a stub or loopback link, or type is not specified)";
      }
    }

    // Use unmodified top-level elements from base grouping
    leaf-list module {
      type string;
      description
        "Default list of optional configuration modules used by this network
         topology. You can use device-level module attribute to override this
         setting for individual nodes. Host nodes do not inherit global
         configuration modules.";
    }
    
    leaf message {
      type string;
      description
        "Help message to display after successful 'netlab initial' or
         'netlab up' commands. You can use this message to tell the end-user
         how to use the lab.";
    }
    
    leaf name {
      type string;
      description
        "Topology name used to name Linux bridges when using libvirt Vagrant
         plugin. If not specified, the first twelve characters of the directory
         name are used (spaces and dots replaced with underscores).";
    }
    
    leaf provider {
      type string;
      description
        "Virtualization provider (libvirt, clab, or external). Default value:
         libvirt.";
    }
    
    leaf version {
      type string;
      description
        "Minimum netlab version required to use this lab topology. You can
         use either a simple version number or Python module version
         specification (example: >= 1.6.3).";
    }
    
    anydata addressing {
      description
        "IPv4 and IPv6 address pools used to address management, loopback,
         LAN, P2P and stub interfaces. This can be specified by users in the
         topology file. The internal pools structure is created during node
         transformation.";
    }
    
    anydata groups {
      description
        "Groups of lab objects (nodes, VLANs, or VRFs) with similar
         attributes. Groups are specified as a dictionary with group names
         as keys. Dictionary values can be either a list of member nodes or a
         dictionary specifying members. Groups can be used to set node/VLAN/VRF
         attributes, set Ansible group variables, or limit the scope of netlab
         commands.";
    }
    
    anydata vlans {
      description
        "VLAN definitions. VLANs are specified as a dictionary with VLAN
         names as keys. Each VLAN can have attributes like mode (bridge, irb,
         route), links (list of links associated with the VLAN), and other
         VLAN-specific settings.";
    }
    
    anydata validate {
      description
        "Lab validation tests. Validation tests are specified as a dictionary
         with test names as keys. Each test can define nodes to test, wait
         conditions, plugins to execute, and expected results.";
    }
    
    anydata prefix {
      description
        "Named IP prefixes that can be used to address links and VLANs or in
         prefix lists or validation expressions. The dictionary keys are
         prefix names (e.g., lan_1, lan_2, loopback); the values are dictionaries
         defining individual prefixes with ipv4, ipv6, pool, and allocation
         attributes (flexible structure).";
    }
    
    container tools {
      description
        "External network management tools deployed after the lab has been
         started and configured. Tools are started as Docker containers and
         can access the management network and management interfaces of lab
         devices.";
      anydata tool_definitions {
        description
          "Tool definitions. Each tool can have runtime, enabled, and
           tool-specific configuration parameters (flexible structure)";
      }
    }
    
    leaf-list plugin {
      type string;
      description
        "List of plugins used by this topology. Plugins extend netlab
         functionality with custom configuration templates, validation tests,
         or other features.";
    }
    
    leaf-list input {
      type string;
      description
        "Input topology file paths (internal). Tracks the source topology
         files used during transformation. Added during the load phase to
         record the main topology file and any included default files.";
    }
    
    anydata Plugin {
      description
        "Plugin internal data (flexible structure). Contains loaded plugin objects
         added during plugin initialization. This is present at init phase
         because plugins are loaded before the init hook is called.";
    }
    
    anydata libvirt {
      description
        "Libvirt-specific topology settings. Can include libvirt-specific
         configuration like bridge names, port mappings, and other
         virtualization provider settings.";
    }
    
    anydata clab {
      description
        "Containerlab-specific topology settings. Can include containerlab-specific
         configuration like network names, container settings, and other
         containerlab provider settings.";
    }
    
    // Module-specific topology-level attributes
    anydata ospf {
      description "OSPF module topology-level attributes";
    }
    anydata bgp {
      description "BGP module topology-level attributes";
    }
    anydata isis {
      description "ISIS module topology-level attributes";
    }
    anydata vlan {
      description "VLAN module topology-level attributes";
    }
    anydata vrf {
      description "VRF module topology-level attributes";
    }
    anydata vrfs {
      description
        "Topology-level VRF definitions. Dictionary of VRF names and their attributes (rd, import, export, loopback, etc.).";
    }

    // Internal data structures (added during transformation)
    anydata Provider {
      description "Provider internal data";
    }
    anydata pools {
      description "Address pools (internal representation)";
    }

    // Note: Cannot validate node count with anydata, but structure is validated
  }
}
